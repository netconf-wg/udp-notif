module ietf-udp-notif-transport {
  yang-version 1.1;
  namespace
    "urn:ietf:params:xml:ns:yang:ietf-udp-notif-transport";
  prefix unt;
  import ietf-subscribed-notifications {
    prefix sn;
    reference
      "RFC 8639: Subscription to YANG Notifications";
  }
  import ietf-subscribed-notif-receivers {
    prefix snr;
    reference
      "RFC YYYY: An HTTPS-based Transport for
                 Configured Subscriptions";
  }
  import ietf-udp-client {
    prefix udpc;
    reference
      "RFC ZZZZ: YANG Grouping for UDP Clients and UDP Servers";
  }
  import ietf-tls-common {
    prefix tlscmn;
    reference
      "RFC 9645: YANG Groupings for TLS Clients and TLS Servers";
  }
  import ietf-tls-client {
    prefix tlsc;
    reference
      "RFC 9645: YANG Groupings for TLS Clients and TLS Servers";
  }

  organization "IETF NETCONF (Network Configuration) Working Group";
  contact
    "WG Web:   <http:/tools.ietf.org/wg/netconf/>
     WG List:  <mailto:netconf@ietf.org>

     Authors:  Guangying Zheng
               <mailto:zhengguangying@huawei.com>
               Tianran Zhou
               <mailto:zhoutianran@huawei.com>
               Thomas Graf
               <mailto:thomas.graf@swisscom.com>
               Pierre Francois
               <mailto:pierre.francois@insa-lyon.fr>
               Alex Huang Feng
               <mailto:alex.huang-feng@insa-lyon.fr>
               Paolo Lucente
               <mailto:paolo@ntt.net>";

  description
    "Defines a model for configuring UDP-Notif as a transport
    for configured subscriptions [RFC8639].

    Copyright (c) 2025 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX
    (https://www.rfc-editor.org/info/rfcXXXX); see the RFC itself
    for full legal notices.";

  revision 2025-02-07 {
    description
      "Initial revision";
    reference
      "RFC XXXX: UDP-based Transport for Configured Subscriptions";
  }
 
 /*
  * FEATURES
  */
  feature encode-cbor {
    description
      "Indicates that CBOR encoding of notification
      messages is supported.";
    reference
      "RFC 9254: CBOR Encoding of Data Modeled with YANG";
  }
  feature dtls13 {
    description
      "Indicates that DTLS 1.3 encryption of UDP
      packets is supported.";
    reference 
      "RFC 9147: The Datagram Transport Layer Security (DTLS)
      Protocol Version 1.3";
  }

 /*
  * IDENTITIES
  */  
  identity udp-notif {
    base sn:transport;
    base sn:configurable-encoding;
    description
      "UDP-Notif is used as transport for notification messages
        and state change notifications.";
  }

  identity encode-cbor {
    base sn:encoding;
    description
      "Encode data using CBOR.";
    reference
      "RFC 9254: CBOR Encoding of Data Modeled with YANG";
  }

  identity unsupported-max-segment-size {
    base sn:establish-subscription-error;
    base sn:modify-subscription-error;
    description
      "Error triggered when the specified value 'max-segment-size'
      is not supported by the publisher. An implementation may
      only support a subset of the uint16.";
    reference
      "RFC XXXX: UDP-based Transport for Configured Subscriptions";
  }

  grouping udp-notif-receiver {
    description
      "Provides a reusable identification of a UDP-Notif target
      receiver.";

    uses udpc:udp-client {
      refine remote-port {
        mandatory true;
      }
    }

    container dtls {
      if-feature dtls13;
      presence dtls;
      uses tlsc:tls-client-grouping {
        // Using tls-client-grouping without TLS1.2 parameters
        // allowing only DTLS 1.3
        refine "client-identity/auth-type/tls12-psk" {
          // create the logical impossibility of enabling TLS1.2
          if-feature "not tlsc:client-ident-tls12-psk";
        }
        refine "server-authentication/tls12-psks" {
          // create the logical impossibility of enabling TLS1.2
          if-feature "not tlsc:server-auth-tls12-psk";
        }
        refine "hello-params/tls-versions/min" {
          must "not(derived-from-or-self(current(), "
            + "'tlscmn:tls12'))" {
            error-message
              "TLS 1.2 is not supported as min TLS version";
          }
        }
        refine "hello-params/tls-versions/max" {
          must "not(derived-from-or-self(current(), "
            + "'tlscmn:tls12'))" {
            error-message
              "TLS 1.2 is not supported as max TLS version";
          }
        }
      }
      description 
        "Container for configuring DTLS 1.3 parameters.";
    }

    leaf enable-segmentation {
      type boolean;
      default true;
      description 
        "When disabled, the publisher will not segment UDP-Notif
        messages and large messages may be fragmented at the IP
        layer.";
    }

    leaf max-segment-size {
      type uint16;
      description 
        "UDP-Notif provides a configurable max-segment-size to
        control the size of each segment (UDP-Notif header, with
        options, included).
        The publisher may trigger an 'unsupported-max-segment-size'
        error if the publisher does not support the configured
        value.";
    }
  }

  augment "/sn:subscriptions/snr:receiver-instances/" +
          "snr:receiver-instance/snr:transport-type" {
    case udp-notif {
      container udp-notif-receiver {
        description
          "The UDP-notif receiver to send notifications to.";
        uses udp-notif-receiver;
      }
    }
    description
      "Augments the transport-type choice to include the 'udp-notif'
       transport.";
  }
}
