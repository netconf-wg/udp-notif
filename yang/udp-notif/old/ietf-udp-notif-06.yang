module ietf-udp-notif {
  yang-version 1.1;
  namespace
    "urn:ietf:params:xml:ns:yang:ietf-udp-notif";
  prefix un;
  import ietf-subscribed-notifications {
    prefix sn;
    reference
      "RFC 8639: Subscription to YANG Notifications";
  }
  import ietf-inet-types {
    prefix inet;
    reference
      "RFC 6991: Common YANG Data Types";
  }
  import ietf-tls-client {
    prefix tlsc;
    reference
      "RFC YYYY: YANG Groupings for TLS Clients and TLS Servers";
  }

  organization "IETF NETCONF (Network Configuration) Working Group";
  contact
    "WG Web:   <http:/tools.ietf.org/wg/netconf/>
     WG List:  <mailto:netconf@ietf.org>

     Authors:  Guangying Zheng
               <mailto:zhengguangying@huawei.com>
               Tianran Zhou
               <mailto:zhoutianran@huawei.com>
               Thomas Graf
               <mailto:thomas.graf@swisscom.com>
               Pierre Francois
               <mailto:pierre.francois@insa-lyon.fr>
               Alex Huang Feng
               <mailto:alex.huang-feng@insa-lyon.fr>
               Paolo Lucente
               <mailto:paolo@ntt.net>";

  description
    "Defines UDP-Notif as a supported transport for subscribed
    event notifications.

    Copyright (c) 2018-2022 IETF Trust and the persons identified as
    authors of the code.  All rights reserved.

    Redistribution and use in source and binary forms, with or without
    modification, is permitted pursuant to, and subject to the license
    terms contained in, the Simplified BSD License set forth in Section
    4.c of the IETF Trust's Legal Provisions Relating to IETF Documents
    (https://trustee.ietf.org/license-info).

    This version of this YANG module is part of RFC XXXX; see the RFC
    itself for full legal notices.";

  revision 2022-05-25 {
    description
      "Added container for DTLS parameters.
      Changed grouping name to 'udp-receiver-grouping'.
      Port made mandatory.
      Added segmentation feature.
      Added dtls-supported feature.
      Changed 'max-segmentation-size' leaf name to 'max-segment-size'.";
    reference
      "RFC XXXX: UDP-based Transport for Configured Subscriptions";
  }
 
 /*
  * FEATURES
  */
  feature encode-cbor {
    description
      "This feature indicates that CBOR encoding of notification
       messages is supported.";
  }
  feature dtls-supported {
    description
      "This feature indicates that DTLS encryption of notification
       messages is supported.";
  }
  feature segmentation {
    description
      "This feature indicates segmentation of notification messages 
      is supported.";
  }

 /*
  * IDENTITIES
  */  
  identity udp-notif {
    base sn:transport;
    description
      "UDP-Notif is used as transport for notification messages
        and state change notifications.";
  }

  identity encode-cbor {
    base sn:encoding;
    description
      "Encode data using CBOR as described in RFC XXX.";
    reference
      "RFC XXX: draft-ietf-core-yang-cbor-18, CBOR Encoding of 
        Data Modeled with YANG";
  }

  grouping udp-receiver-grouping {
    description
      "Provides a reusable description of a UDP-Notif target
      receiver.";

    leaf address {
      type inet:ip-address;
      mandatory true;
      description
        "IP address of target UDP-Notif receiver, which can be an
        IPv4 address or an IPV6 address.";
    }
  
    leaf port {
      type inet:port-number;
      mandatory true;
      description
        "Port number of target UDP-Notif receiver.";
    }

    leaf enable-segmentation {
      if-feature segmentation;
      type boolean;
      default false;
      description 
        "The switch for the segmentation feature. When disabled, the
        publisher will not allow fragment for a very large data";
    }

    leaf max-segment-size {
      when "../enable-segmentation = 'true'";
      if-feature segmentation;
      type uint32;
      description 
        "UDP-Notif provides a configurable max-segment-size to
        control the size of each segment (UDP-Notif header, with
        options, included).";
    }

    leaf enable-dtls {
      if-feature dtls-supported;
      type boolean;
      default false;
      description
        "The switch for the DTLS encryption feature. When disabled, the
        publisher will not encrypt UDP-Notif messages.";
    }

    container dtls {
      when "../enable-dtls = 'true'";
      if-feature dtls-supported;
      uses tlsc:tls-client-grouping;
      description 
        "Container for configuring DTLS parameters if DTLS is enabled.";
    }
  }

  augment "/sn:subscriptions/sn:subscription/sn:receivers/sn:receiver" {
    when "derived-from(../../transport, 'un:udp-notif')";
    description
      "This augmentation allows UDP-Notif specific parameters to be
       exposed for a subscription.";

    uses udp-receiver-grouping;
  }
}
