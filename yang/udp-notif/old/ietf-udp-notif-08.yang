module ietf-udp-notif {
  yang-version 1.1;
  namespace
    "urn:ietf:params:xml:ns:yang:ietf-udp-notif";
  prefix un;
  import ietf-subscribed-notifications {
    prefix sn;
    reference
      "RFC 8639: Subscription to YANG Notifications";
  }
  import ietf-inet-types {
    prefix inet;
    reference
      "RFC 6991: Common YANG Data Types";
  }
  import ietf-tls-client {
    prefix tlsc;
    reference
      "RFC YYYY: YANG Groupings for TLS Clients and TLS Servers";
  }

  organization "IETF NETCONF (Network Configuration) Working Group";
  contact
    "WG Web:   <http:/tools.ietf.org/wg/netconf/>
     WG List:  <mailto:netconf@ietf.org>

     Authors:  Guangying Zheng
               <mailto:zhengguangying@huawei.com>
               Tianran Zhou
               <mailto:zhoutianran@huawei.com>
               Thomas Graf
               <mailto:thomas.graf@swisscom.com>
               Pierre Francois
               <mailto:pierre.francois@insa-lyon.fr>
               Alex Huang Feng
               <mailto:alex.huang-feng@insa-lyon.fr>
               Paolo Lucente
               <mailto:paolo@ntt.net>";

  description
    "Defines UDP-Notif as a supported transport for subscribed
    event notifications.

    Copyright (c) 2022 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX; see the RFC
    itself for full legal notices.";

  revision 2022-08-29 {
    description
      "Removed enable-dtls leaf and changed container dtls to presence container.
      Removed TLS1.2 references from tls-client-grouping";
    reference
      "RFC XXXX: UDP-based Transport for Configured Subscriptions";
  }
 
 /*
  * FEATURES
  */
  feature encode-cbor {
    description
      "This feature indicates that CBOR encoding of notification
       messages is supported.";
  }
  feature dtls-supported {
    description
      "This feature indicates that DTLS encryption of notification
       messages is supported.";
  }
  feature segmentation {
    description
      "This feature indicates segmentation of notification messages 
      is supported.";
  }

 /*
  * IDENTITIES
  */  
  identity udp-notif {
    base sn:transport;
    description
      "UDP-Notif is used as transport for notification messages
        and state change notifications.";
  }

  identity encode-cbor {
    base sn:encoding;
    description
      "Encode data using CBOR as described in RFC 9254.";
    reference
      "RFC 9254: CBOR Encoding of Data Modeled with YANG";
  }

  grouping udp-receiver-grouping {
    description
      "Provides a reusable description of a UDP-Notif target
      receiver.";

    leaf address {
      type inet:ip-address;
      mandatory true;
      description
        "IP address of target UDP-Notif receiver, which can be an
        IPv4 address or an IPV6 address.";
    }
  
    leaf port {
      type inet:port-number;
      mandatory true;
      description
        "Port number of target UDP-Notif receiver.";
    }

    leaf enable-segmentation {
      if-feature segmentation;
      type boolean;
      default false;
      description 
        "The switch for the segmentation feature. When disabled, the
        publisher will not allow fragment for a very large data";
    }

    leaf max-segment-size {
      when "../enable-segmentation = 'true'";
      if-feature segmentation;
      type uint32;
      description 
        "UDP-Notif provides a configurable max-segment-size to
        control the size of each segment (UDP-Notif header, with
        options, included).";
    }

    container dtls {
      if-feature dtls-supported;
      presence dtls;
      uses tlsc:tls-client-grouping {
        // Using tls-client-grouping without TLS1.2 parameters
        // allowing only DTLS 1.3
        refine "client-identity/auth-type/tls12-psk" {
          // create the logical impossibility of enabling TLS1.2
          if-feature "not tlsc:client-ident-tls12-psk";
        }
        refine "server-authentication/tls12-psks" {
          // create the logical impossibility of enabling TLS1.2
          if-feature "not tlsc:server-auth-tls12-psk";
        }
      }
      description 
        "Container for configuring DTLS 1.3 parameters if DTLS is enabled.";
    }
  }

  augment "/sn:subscriptions/sn:subscription/sn:receivers/sn:receiver" {
    when "derived-from(../../transport, 'un:udp-notif')";
    description
      "This augmentation allows UDP-Notif specific parameters to be
       exposed for a subscription.";

    uses udp-receiver-grouping;
  }
}
